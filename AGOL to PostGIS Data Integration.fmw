FME workspace AGOL to PostGIS Data Integration.fmw

Parameters:
- SourceDataset_POSTGIS = nbi_fme_test_import   # Connection
- DestDataset_POSTGIS = nbi_fme_test_import   # Connection

Readers:
- POSTGIS_3: POSTGIS from $(SourceDataset_POSTGIS)
- ARCGISONLINEFEATURES_2: ARCGISONLINEFEATURES

Writers:
- POSTGIS_2: POSTGIS to $(DestDataset_POSTGIS)

Bookmark: Fibre Drop
fibre_drop (reader POSTGIS_3)
    attributes: inport_date varchar(200), modified_date varchar(200), OBJECTID int4, label varchar(17), drop_code int2, route_surv int2, cross_oh int2, cross_ug int2, cross_prop int2, duct_stat int2, calc_lengt float8, ribbon varchar(5), comments varchar(255), globalid varchar(38), createdby varchar(255), creationdate timestamp, editedby varchar(255), editeddate timestamp, Shape__Length float8, _part_count numeric(20,0)
    -> BulkAttributeRenamer_11
BulkAttributeRenamer_11
    ATTRCHOICE_ACTION = NONPROTECTEDFME
    MODE_CHOICE = RENAME
    PATTERN_ACTION_DISP = ADDPREFIX
    REPLACE_STR = post_
    ATTRCHOICE = All Attributes
    -> DateTimeConverter_8
DateTimeConverter_8
    DATETIME_ATTR = post_modified_date
    IN_FORMAT = %Y%m%d%H%M
    OUT_FORMAT = %Y%m%d%H%M%S
    PASSTHROUGH = YES
    REPAIR_INPUT = YES
    -> FeatureMerger_4 [REQUESTOR]
Build_FibreDrop (reader ARCGISONLINEFEATURES_2)
    attributes: OBJECTID OID, label String(17), drop_code SmallInteger, route_surv SmallInteger, cross_oh SmallInteger, cross_ug SmallInteger, cross_prop SmallInteger, duct_stat SmallInteger, calc_lengt Double, ribbon String(5), comments String(255), globalid GlobalID(38), createdby String(255), creationdate Date, editedby String(255), editeddate Date, Shape__Length Double
    -> BulkAttributeRenamer_10
BulkAttributeRenamer_10
    ATTRCHOICE_ACTION = NONPROTECTEDFME
    MODE_CHOICE = RENAME
    PATTERN_ACTION_DISP = ADDPREFIX
    REPLACE_STR = agol_
    ATTRCHOICE = All Attributes
    -> DateTimeConverter_9
DateTimeConverter_9
    DATETIME_ATTR = agol_editeddate
    IN_FORMAT = %Y%m%d%H%M
    OUT_FORMAT = %Y%m%d%H%M%S
    PASSTHROUGH = YES
    REPAIR_INPUT = YES
    -> FeatureMerger_4 [SUPPLIER]
FeatureMerger_4
    ATTR_ACCUM_MODE = Merge Supplier
    ATTR_CONFLICT_RES_LOOKUP = SUPPLIER_IF_CONFLICT
    IGNORE_NULLS = No
    JOIN_KEYS = @Value(post_globalid) @Value(agol_globalid) AUTO
    MERGE_TYPE_VAL = GEOM_AND_ATTRS
    PRESERVE_FEATURE_ORDER_LOOKUP = PER_OUTPUT_PORT
    PROCESS_DUPS = NO
    REJECT_NULL_MISSING_KEYS = No
    SUPPLIERS_FIRST = No
    ATTR_CONFLICT_RES = Use Supplier
    MERGE_TYPE = Attributes and Geometry
    MERGED -> Tester_4
Tester_4
    BOOL_OP = OR
    TEST_CLAUSE = DATETIME_TEST @Value(agol_editeddate) > @Value(post_modified_date)
    TEST_MODE = DATETIME_TEST
    PASSED -> BulkAttributeRemover_4
BulkAttributeRemover_4
    ATTR_EXP = post_
    -> BulkAttributeRenamer_12
BulkAttributeRenamer_12
    ATTRCHOICE_ACTION = NONPROTECTEDFME
    CASE_DISP = YES
    MODE_CHOICE = RENAME
    PATTERN_ACTION_DISP = REMOVEPREFIX
    REPLACE_STR = agol_
    ATTRCHOICE = All Attributes
    -> AttributeManager_4
AttributeManager_4
    ATTR_TABLE = RENAME_SET_VALUE OBJECTID > objectid
    USER_EXPOSED_ATTRIBUTES = agol_OBJECTID,agol_level_,agol_homes,agol_name,agol_GlobalID,agol_CreatedBy,agol_CreationDate,agol_EditedBy,agol_EditedDate,agol_Shape__Area,agol_Shape__Length,post_inport_date,post_modified_date,post_level,post_OBJECTID,post_homes,post_name,post_GlobalID,post_CreatedBy,post_CreationDate,post_EditedBy,post_EditedDate,post_Shape__Area,post_Shape__Length,OBJECTID,level_,homes,name,GlobalID,CreatedBy,CreationDate,EditedBy,EditedDate,Shape__Area,Shape__Length,status,label,ownership,type,location_a,surface_ty,comments,drop_tag,visible,use_,ch_access,condition,lid_con,duct_cou,reason_for,dp_capacit,nbi_enc,ch_area,exchange,dub_pro,eir_label,start_end,sd_meet,nbi_sd,cut_con,hazard,ribbon,build_status,design_status,asb_core,asb_label,build_com,bldg_id,address,eircode,address_st,hhp_res,hhp_com,floors,new_prem,odp_label,prem_status,drop_code,route_surv,cross_oh,cross_ug,cross_prop,duct_stat,calc_lengt,globalid,createdby,creationdate,editedby,editeddate
    -> fibre_drop (writer POSTGIS_2)
fibre_drop (writer POSTGIS_2)
    attributes: inport_date varchar(200), modified_date varchar(200), objectid int4, label varchar(17), drop_code int2, route_surv int2, cross_oh int2, cross_ug int2, cross_prop int2, duct_stat int2, calc_lengt float8, ribbon varchar(5), comments varchar(255), globalid varchar(38), createdby varchar(255), creationdate timestamp, editedby varchar(255), editeddate timestamp, shape__length float8, _part_count numeric(20,0)

Bookmark: FibreDuct
fibre_duct (reader POSTGIS_3)
    attributes: inport_date varchar(200), modified_date varchar(200), use int2, OBJECTID int4, status int2, owner int2, duct_label varchar(24), cont_cable varchar(100), duct_type int2, duct_size int2, sub_size int2, length float8, location_a int2, roped int2, spa_sd int2, sub_cap int2, el_cross_v int2, surface_ty int2, sd_no int2, eir_sd int2, sd_area int2, exchange varchar(5), dub_pro int2, sd_status int2, sd_descrip int2, duct_reas int2, pri_way int2, duct_pub float8, duct_pri float8, duct_notes varchar(255),
      ribbon varchar(5), ipid varchar(13), a_end_ipid varchar(13), b_end_ipid varchar(13), build_status int2, design_status int2, asb_bflen float4, asb_dlen float4, asb_sdlen float4, asb_ohlen float4, asb_uglen float4, asb_label varchar(24), build_com varchar(255), globalid varchar(38), createdby varchar(255), creationdate timestamp, editedby varchar(255), editeddate timestamp, Shape__Length float8, _part_count numeric(20,0), way_type int2
    -> BulkAttributeRenamer_14
BulkAttributeRenamer_14
    ATTRCHOICE_ACTION = NONPROTECTEDFME
    MODE_CHOICE = RENAME
    PATTERN_ACTION_DISP = ADDPREFIX
    REPLACE_STR = post_
    ATTRCHOICE = All Attributes
    -> DateTimeConverter_10
DateTimeConverter_10
    DATETIME_ATTR = post_modified_date
    IN_FORMAT = %Y%m%d%H%M
    OUT_FORMAT = %Y%m%d%H%M%S
    PASSTHROUGH = YES
    REPAIR_INPUT = YES
    -> FeatureMerger_5 [REQUESTOR]
Build_FibreDuct (reader ARCGISONLINEFEATURES_2)
    attributes: OBJECTID OID, status SmallInteger, owner SmallInteger, duct_label String(24), cont_cable String(100), duct_type SmallInteger, duct_size SmallInteger, sub_size SmallInteger, length Double, location_a SmallInteger, roped SmallInteger, spa_sd SmallInteger, sub_cap SmallInteger, el_cross_v SmallInteger, surface_ty SmallInteger, sd_no SmallInteger, eir_sd SmallInteger, use_ SmallInteger, sd_area SmallInteger, exchange String(5), dub_pro SmallInteger, sd_status SmallInteger, sd_descrip SmallInteger, duct_reas SmallInteger, pri_way SmallInteger, duct_pub Double, duct_pri Double, duct_notes String(255), ribbon String(5), ipid String(13),
      a_end_ipid String(13), b_end_ipid String(13), build_status SmallInteger, design_status SmallInteger, asb_bflen Single, asb_dlen Single, asb_sdlen Single, asb_ohlen Single, asb_uglen Single, asb_label String(24), build_com String(255), globalid GlobalID(38), createdby String(255), creationdate Date, editedby String(255), editeddate Date, Shape__Length Double
    -> BulkAttributeRenamer_13
BulkAttributeRenamer_13
    ATTRCHOICE_ACTION = NONPROTECTEDFME
    MODE_CHOICE = RENAME
    PATTERN_ACTION_DISP = ADDPREFIX
    REPLACE_STR = agol_
    ATTRCHOICE = All Attributes
    -> DateTimeConverter_11
DateTimeConverter_11
    DATETIME_ATTR = agol_editeddate
    IN_FORMAT = %Y%m%d%H%M
    OUT_FORMAT = %Y%m%d%H%M%S
    PASSTHROUGH = YES
    REPAIR_INPUT = YES
    -> FeatureMerger_5 [SUPPLIER]
FeatureMerger_5
    ATTR_ACCUM_MODE = Merge Supplier
    ATTR_CONFLICT_RES_LOOKUP = SUPPLIER_IF_CONFLICT
    IGNORE_NULLS = No
    JOIN_KEYS = @Value(post_globalid) @Value(agol_globalid) AUTO
    MERGE_TYPE_VAL = GEOM_AND_ATTRS
    PRESERVE_FEATURE_ORDER_LOOKUP = PER_OUTPUT_PORT
    PROCESS_DUPS = NO
    REJECT_NULL_MISSING_KEYS = No
    SUPPLIERS_FIRST = No
    ATTR_CONFLICT_RES = Use Supplier
    MERGE_TYPE = Attributes and Geometry
    MERGED -> Tester_5
Tester_5
    BOOL_OP = OR
    TEST_CLAUSE = DATETIME_TEST @Value(agol_editeddate) > @Value(post_modified_date)
    TEST_MODE = DATETIME_TEST
    PASSED -> BulkAttributeRemover_5
BulkAttributeRemover_5
    ATTR_EXP = post_
    -> BulkAttributeRenamer_15
BulkAttributeRenamer_15
    ATTRCHOICE_ACTION = NONPROTECTEDFME
    CASE_DISP = YES
    MODE_CHOICE = RENAME
    PATTERN_ACTION_DISP = REMOVEPREFIX
    REPLACE_STR = agol_
    ATTRCHOICE = All Attributes
    -> AttributeManager_5
AttributeManager_5
    ATTR_TABLE:
      RENAME_SET_VALUE OBJECTID > objectid
      RENAME_SET_VALUE use_ > use
    USER_EXPOSED_ATTRIBUTES = agol_OBJECTID,agol_level_,agol_homes,agol_name,agol_GlobalID,agol_CreatedBy,agol_CreationDate,agol_EditedBy,agol_EditedDate,agol_Shape__Area,agol_Shape__Length,post_inport_date,post_modified_date,post_level,post_OBJECTID,post_homes,post_name,post_GlobalID,post_CreatedBy,post_CreationDate,post_EditedBy,post_EditedDate,post_Shape__Area,post_Shape__Length,OBJECTID,level_,homes,name,GlobalID,CreatedBy,CreationDate,EditedBy,EditedDate,Shape__Area,Shape__Length,status,label,ownership,type,location_a,surface_ty,comments,drop_tag,visible,use_,ch_access,condition,lid_con,duct_cou,reason_for,dp_capacit,nbi_enc,ch_area,exchange,dub_pro,eir_label,start_end,sd_meet,nbi_sd,cut_con,hazard,ribbon,build_status,design_status,asb_core,asb_label,build_com,bldg_id,address,eircode,address_st,hhp_res,hhp_com,floors,new_prem,odp_label,prem_status,drop_code,route_surv,cross_oh,cross_ug,cross_prop,duct_stat,calc_lengt,owner,duct_label,cont_cable,duct_type,duct_size,sub_size,length,roped,spa_sd,sub_cap,el_cross_v,sd_no,eir_sd,sd_area,sd_status,sd_descrip,duct_reas,pri_way,duct_pub,duct_pri,duct_notes,ipid,a_end_ipid,b_end_ipid,asb_bflen,asb_dlen,asb_sdlen,asb_ohlen,asb_uglen,globalid,createdby,creationdate,editedby,editeddate
    -> fibre_duct (writer POSTGIS_2)
fibre_duct (writer POSTGIS_2)
    attributes: inport_date varchar(200), modified_date varchar(200), use int2, objectid int4, status int2, owner int2, duct_label varchar(24), cont_cable varchar(100), duct_type int2, duct_size int2, sub_size int2, length float8, location_a int2, roped int2, spa_sd int2, sub_cap int2, el_cross_v int2, surface_ty int2, sd_no int2, eir_sd int2, sd_area int2, exchange varchar(5), dub_pro int2, sd_status int2, sd_descrip int2, duct_reas int2, pri_way int2, duct_pub float8, duct_pri float8, duct_notes varchar(255),
      ribbon varchar(5), ipid varchar(13), a_end_ipid varchar(13), b_end_ipid varchar(13), build_status int2, design_status int2, asb_bflen float4, asb_dlen float4, asb_sdlen float4, asb_ohlen float4, asb_uglen float4, asb_label varchar(24), build_com varchar(255), globalid varchar(38), createdby varchar(255), creationdate timestamp, editedby varchar(255), editeddate timestamp, shape__length float8, _part_count numeric(20,0)

Bookmark: FibreSheath
fibre_sheath (reader POSTGIS_3)
    attributes: inport_date varchar(200), modified_date varchar(200), OBJECTID int4, label varchar(14), type int2, calc_lengt float8, meas_lengt float8, from_ varchar(8), placement int2, backhaul int2, ug_adss float8, ribbon varchar(5), comments varchar(255), build_status int2, design_status int2, asb_len float4, asb_ohlen float4, asb_uglen float4, asb_label varchar(14), build_com varchar(255), globalid varchar(38), createdby varchar(255), creationdate timestamp, editedby varchar(255), editeddate timestamp, Shape__Length float8, _part_count numeric(20,0)
    -> BulkAttributeRenamer_17
BulkAttributeRenamer_17
    ATTRCHOICE_ACTION = NONPROTECTEDFME
    MODE_CHOICE = RENAME
    PATTERN_ACTION_DISP = ADDPREFIX
    REPLACE_STR = post_
    ATTRCHOICE = All Attributes
    -> DateTimeConverter_12
DateTimeConverter_12
    DATETIME_ATTR = post_modified_date
    IN_FORMAT = %Y%m%d%H%M
    OUT_FORMAT = %Y%m%d%H%M%S
    PASSTHROUGH = YES
    REPAIR_INPUT = YES
    -> FeatureMerger_6 [REQUESTOR]
Build_FibreSheath (reader ARCGISONLINEFEATURES_2)
    attributes: OBJECTID OID, label String(14), type SmallInteger, calc_lengt Double, meas_lengt Double, from_ String(8), placement SmallInteger, backhaul SmallInteger, ug_adss Double, ribbon String(5), comments String(255), build_status SmallInteger, design_status SmallInteger, asb_len Single, asb_ohlen Single, asb_uglen Single, asb_label String(14), build_com String(255), globalid GlobalID(38), createdby String(255), creationdate Date, editedby String(255), editeddate Date, Shape__Length Double
    -> BulkAttributeRenamer_16
BulkAttributeRenamer_16
    ATTRCHOICE_ACTION = NONPROTECTEDFME
    MODE_CHOICE = RENAME
    PATTERN_ACTION_DISP = ADDPREFIX
    REPLACE_STR = agol_
    ATTRCHOICE = All Attributes
    -> DateTimeConverter_13
DateTimeConverter_13
    DATETIME_ATTR = agol_editeddate
    IN_FORMAT = %Y%m%d%H%M
    OUT_FORMAT = %Y%m%d%H%M%S
    PASSTHROUGH = YES
    REPAIR_INPUT = YES
    -> FeatureMerger_6 [SUPPLIER]
FeatureMerger_6
    ATTR_ACCUM_MODE = Merge Supplier
    ATTR_CONFLICT_RES_LOOKUP = SUPPLIER_IF_CONFLICT
    IGNORE_NULLS = No
    JOIN_KEYS = @Value(post_globalid) @Value(agol_globalid) AUTO
    MERGE_TYPE_VAL = GEOM_AND_ATTRS
    PRESERVE_FEATURE_ORDER_LOOKUP = PER_OUTPUT_PORT
    PROCESS_DUPS = NO
    REJECT_NULL_MISSING_KEYS = No
    SUPPLIERS_FIRST = No
    ATTR_CONFLICT_RES = Use Supplier
    MERGE_TYPE = Attributes and Geometry
    MERGED -> Tester_6
Tester_6
    BOOL_OP = OR
    TEST_CLAUSE = DATETIME_TEST @Value(agol_editeddate) > @Value(post_modified_date)
    TEST_MODE = DATETIME_TEST
    PASSED -> BulkAttributeRemover_6
BulkAttributeRemover_6
    ATTR_EXP = post_
    -> BulkAttributeRenamer_18
BulkAttributeRenamer_18
    ATTRCHOICE_ACTION = NONPROTECTEDFME
    CASE_DISP = YES
    MODE_CHOICE = RENAME
    PATTERN_ACTION_DISP = REMOVEPREFIX
    REPLACE_STR = agol_
    ATTRCHOICE = All Attributes
    -> AttributeManager_6
AttributeManager_6
    ATTR_TABLE = RENAME_SET_VALUE OBJECTID > objectid
    USER_EXPOSED_ATTRIBUTES = agol_OBJECTID,agol_level_,agol_homes,agol_name,agol_GlobalID,agol_CreatedBy,agol_CreationDate,agol_EditedBy,agol_EditedDate,agol_Shape__Area,agol_Shape__Length,post_inport_date,post_modified_date,post_level,post_OBJECTID,post_homes,post_name,post_GlobalID,post_CreatedBy,post_CreationDate,post_EditedBy,post_EditedDate,post_Shape__Area,post_Shape__Length,OBJECTID,level_,homes,name,GlobalID,CreatedBy,CreationDate,EditedBy,EditedDate,Shape__Area,Shape__Length,status,label,ownership,type,location_a,surface_ty,comments,drop_tag,visible,use_,ch_access,condition,lid_con,duct_cou,reason_for,dp_capacit,nbi_enc,ch_area,exchange,dub_pro,eir_label,start_end,sd_meet,nbi_sd,cut_con,hazard,ribbon,build_status,design_status,asb_core,asb_label,build_com,bldg_id,address,eircode,address_st,hhp_res,hhp_com,floors,new_prem,odp_label,prem_status,drop_code,route_surv,cross_oh,cross_ug,cross_prop,duct_stat,calc_lengt,meas_lengt,from_,placement,backhaul,ug_adss,asb_len,asb_ohlen,asb_uglen,globalid,createdby,creationdate,editedby,editeddate
    -> fibre_sheath (writer POSTGIS_2)
fibre_sheath (writer POSTGIS_2)
    attributes: inport_date varchar(200), modified_date varchar(200), objectid int4, label varchar(14), type int2, calc_lengt float8, meas_lengt float8, from_ varchar(8), placement int2, backhaul int2, ug_adss float8, ribbon varchar(5), comments varchar(255), build_status int2, design_status int2, asb_len float4, asb_ohlen float4, asb_uglen float4, asb_label varchar(14), build_com varchar(255), globalid varchar(38), createdby varchar(255), creationdate timestamp, editedby varchar(255), editeddate timestamp, shape__length float8, _part_count numeric(20,0)

Bookmark: FibreSlack
fibre_slack (reader POSTGIS_3)
    attributes: inport_date varchar(200), modified_date varchar(200), OBJECTID int4, label varchar(16), cab_label varchar(14), length int2, ribbon varchar(5), comments varchar(255), build_status int2, design_status int2, asb_len float4, asb_label varchar(14), build_com varchar(255), globalid varchar(38), createdby varchar(255), creationdate timestamp, editedby varchar(255), editeddate timestamp
    -> BulkAttributeRenamer_20
BulkAttributeRenamer_20
    ATTRCHOICE_ACTION = NONPROTECTEDFME
    MODE_CHOICE = RENAME
    PATTERN_ACTION_DISP = ADDPREFIX
    REPLACE_STR = post_
    ATTRCHOICE = All Attributes
    -> DateTimeConverter_14
DateTimeConverter_14
    DATETIME_ATTR = post_modified_date
    IN_FORMAT = %Y%m%d%H%M
    OUT_FORMAT = %Y%m%d%H%M%S
    PASSTHROUGH = YES
    REPAIR_INPUT = YES
    -> FeatureMerger_7 [REQUESTOR]
Build_FibreSlack (reader ARCGISONLINEFEATURES_2)
    attributes: OBJECTID OID, label String(16), cab_label String(14), length SmallInteger, ribbon String(5), comments String(255), build_status SmallInteger, design_status SmallInteger, asb_len Single, asb_label String(14), build_com String(255), globalid GlobalID(38), createdby String(255), creationdate Date, editedby String(255), editeddate Date
    -> BulkAttributeRenamer_19
BulkAttributeRenamer_19
    ATTRCHOICE_ACTION = NONPROTECTEDFME
    MODE_CHOICE = RENAME
    PATTERN_ACTION_DISP = ADDPREFIX
    REPLACE_STR = agol_
    ATTRCHOICE = All Attributes
    -> DateTimeConverter_15
DateTimeConverter_15
    DATETIME_ATTR = agol_editeddate
    IN_FORMAT = %Y%m%d%H%M
    OUT_FORMAT = %Y%m%d%H%M%S
    PASSTHROUGH = YES
    REPAIR_INPUT = YES
    -> FeatureMerger_7 [SUPPLIER]
FeatureMerger_7
    ATTR_ACCUM_MODE = Merge Supplier
    ATTR_CONFLICT_RES_LOOKUP = SUPPLIER_IF_CONFLICT
    IGNORE_NULLS = No
    JOIN_KEYS = @Value(post_globalid) @Value(agol_globalid) AUTO
    MERGE_TYPE_VAL = GEOM_AND_ATTRS
    PRESERVE_FEATURE_ORDER_LOOKUP = PER_OUTPUT_PORT
    PROCESS_DUPS = NO
    REJECT_NULL_MISSING_KEYS = No
    SUPPLIERS_FIRST = No
    ATTR_CONFLICT_RES = Use Supplier
    MERGE_TYPE = Attributes and Geometry
    MERGED -> Tester_7
Tester_7
    BOOL_OP = OR
    TEST_CLAUSE = DATETIME_TEST @Value(agol_editeddate) > @Value(post_modified_date)
    TEST_MODE = DATETIME_TEST
    PASSED -> BulkAttributeRemover_7
BulkAttributeRemover_7
    ATTR_EXP = post_
    -> BulkAttributeRenamer_21
BulkAttributeRenamer_21
    ATTRCHOICE_ACTION = NONPROTECTEDFME
    CASE_DISP = YES
    MODE_CHOICE = RENAME
    PATTERN_ACTION_DISP = REMOVEPREFIX
    REPLACE_STR = agol_
    ATTRCHOICE = All Attributes
    -> AttributeManager_7
AttributeManager_7
    ATTR_TABLE = RENAME_SET_VALUE OBJECTID > objectid
    USER_EXPOSED_ATTRIBUTES = agol_OBJECTID,agol_level_,agol_homes,agol_name,agol_GlobalID,agol_CreatedBy,agol_CreationDate,agol_EditedBy,agol_EditedDate,agol_Shape__Area,agol_Shape__Length,post_inport_date,post_modified_date,post_level,post_OBJECTID,post_homes,post_name,post_GlobalID,post_CreatedBy,post_CreationDate,post_EditedBy,post_EditedDate,post_Shape__Area,post_Shape__Length,OBJECTID,level_,homes,name,GlobalID,CreatedBy,CreationDate,EditedBy,EditedDate,Shape__Area,Shape__Length,status,label,ownership,type,location_a,surface_ty,comments,drop_tag,visible,use_,ch_access,condition,lid_con,duct_cou,reason_for,dp_capacit,nbi_enc,ch_area,exchange,dub_pro,eir_label,start_end,sd_meet,nbi_sd,cut_con,hazard,ribbon,build_status,design_status,asb_core,asb_label,build_com,bldg_id,address,eircode,address_st,hhp_res,hhp_com,floors,new_prem,odp_label,prem_status,drop_code,route_surv,cross_oh,cross_ug,cross_prop,duct_stat,calc_lengt,cab_label,length,asb_len,globalid,createdby,creationdate,editedby,editeddate
    -> fibre_slack (writer POSTGIS_2)
fibre_slack (writer POSTGIS_2)
    attributes: inport_date varchar(200), modified_date varchar(200), objectid int4, label varchar(16), cab_label varchar(14), length int2, ribbon varchar(5), comments varchar(255), build_status int2, design_status int2, asb_len float4, asb_label varchar(14), build_com varchar(255), globalid varchar(38), createdby varchar(255), creationdate timestamp, editedby varchar(255), editeddate timestamp

Bookmark: Customer Building
customer_buildings (reader POSTGIS_3)
    attributes: inport_date varchar(200), modified_date varchar(200), OBJECTID int4, bldg_id varchar(12), address varchar(255), eircode varchar(7), address_st int2, hhp_res int2, hhp_com int2, floors int2, ribbon varchar(5), new_prem int2, odp_label varchar(8), drop_tag varchar(20), comments varchar(255), prem_status int2, design_status int2, def_reas int2, resolve int2, build_com varchar(255), globalid varchar(38), createdby varchar(255), creationdate timestamp, editedby varchar(255), editeddate timestamp
    -> BulkAttributeRenamer_8
BulkAttributeRenamer_8
    ATTRCHOICE_ACTION = NONPROTECTEDFME
    MODE_CHOICE = RENAME
    PATTERN_ACTION_DISP = ADDPREFIX
    REPLACE_STR = post_
    ATTRCHOICE = All Attributes
    -> DateTimeConverter_6
DateTimeConverter_6
    DATETIME_ATTR = post_modified_date
    IN_FORMAT = %Y%m%d%H%M
    OUT_FORMAT = %Y%m%d%H%M%S
    PASSTHROUGH = YES
    REPAIR_INPUT = YES
    -> FeatureMerger_3 [REQUESTOR]
Build_CustomerBuildings (reader ARCGISONLINEFEATURES_2)
    attributes: OBJECTID OID, bldg_id String(12), address String(255), eircode String(7), address_st SmallInteger, hhp_res SmallInteger, hhp_com SmallInteger, floors SmallInteger, ribbon String(5), new_prem SmallInteger, odp_label String(8), drop_tag String(20), comments String(255), prem_status SmallInteger, design_status SmallInteger, def_reas SmallInteger, resolve SmallInteger, build_com String(255), globalid GlobalID(38), createdby String(255), creationdate Date, editedby String(255), editeddate Date
    -> BulkAttributeRenamer_7
BulkAttributeRenamer_7
    ATTRCHOICE_ACTION = NONPROTECTEDFME
    MODE_CHOICE = RENAME
    PATTERN_ACTION_DISP = ADDPREFIX
    REPLACE_STR = agol_
    ATTRCHOICE = All Attributes
    -> DateTimeConverter_7
DateTimeConverter_7
    DATETIME_ATTR = agol_editeddate
    IN_FORMAT = %Y%m%d%H%M
    OUT_FORMAT = %Y%m%d%H%M%S
    PASSTHROUGH = YES
    REPAIR_INPUT = YES
    -> FeatureMerger_3 [SUPPLIER]
FeatureMerger_3
    ATTR_ACCUM_MODE = Merge Supplier
    ATTR_CONFLICT_RES_LOOKUP = SUPPLIER_IF_CONFLICT
    IGNORE_NULLS = No
    JOIN_KEYS = @Value(post_globalid) @Value(agol_globalid) AUTO
    MERGE_TYPE_VAL = GEOM_AND_ATTRS
    PRESERVE_FEATURE_ORDER_LOOKUP = PER_OUTPUT_PORT
    PROCESS_DUPS = NO
    REJECT_NULL_MISSING_KEYS = No
    SUPPLIERS_FIRST = No
    ATTR_CONFLICT_RES = Use Supplier
    MERGE_TYPE = Attributes and Geometry
    MERGED -> Tester_3
Tester_3
    BOOL_OP = OR
    TEST_CLAUSE = DATETIME_TEST @Value(agol_editeddate) > @Value(post_modified_date)
    TEST_MODE = DATETIME_TEST
    PASSED -> BulkAttributeRemover_3
BulkAttributeRemover_3
    ATTR_EXP = post_
    -> BulkAttributeRenamer_9
BulkAttributeRenamer_9
    ATTRCHOICE_ACTION = NONPROTECTEDFME
    CASE_DISP = YES
    MODE_CHOICE = RENAME
    PATTERN_ACTION_DISP = REMOVEPREFIX
    REPLACE_STR = agol_
    ATTRCHOICE = All Attributes
    -> AttributeManager_3
AttributeManager_3
    ATTR_TABLE = RENAME_SET_VALUE OBJECTID > objectid
    USER_EXPOSED_ATTRIBUTES = agol_OBJECTID,agol_level_,agol_homes,agol_name,agol_GlobalID,agol_CreatedBy,agol_CreationDate,agol_EditedBy,agol_EditedDate,agol_Shape__Area,agol_Shape__Length,post_inport_date,post_modified_date,post_level,post_OBJECTID,post_homes,post_name,post_GlobalID,post_CreatedBy,post_CreationDate,post_EditedBy,post_EditedDate,post_Shape__Area,post_Shape__Length,OBJECTID,level_,homes,name,GlobalID,CreatedBy,CreationDate,EditedBy,EditedDate,Shape__Area,Shape__Length,status,label,ownership,type,location_a,surface_ty,comments,drop_tag,visible,use_,ch_access,condition,lid_con,duct_cou,reason_for,dp_capacit,nbi_enc,ch_area,exchange,dub_pro,eir_label,start_end,sd_meet,nbi_sd,cut_con,hazard,ribbon,build_status,design_status,asb_core,asb_label,build_com,bldg_id,address,eircode,address_st,hhp_res,hhp_com,floors,new_prem,odp_label,prem_status,def_reas,resolve,globalid,createdby,creationdate,editedby,editeddate
    -> customer_buildings (writer POSTGIS_2)
customer_buildings (writer POSTGIS_2)
    attributes: inport_date varchar(200), modified_date varchar(200), objectid int4, bldg_id varchar(12), address varchar(255), eircode varchar(7), address_st int2, hhp_res int2, hhp_com int2, floors int2, ribbon varchar(5), new_prem int2, odp_label varchar(8), drop_tag varchar(20), comments varchar(255), prem_status int2, design_status int2, def_reas int2, resolve int2, build_com varchar(255), globalid varchar(38), createdby varchar(255), creationdate timestamp, editedby varchar(255), editeddate timestamp

Bookmark: OLT
olt (reader POSTGIS_3)
    attributes: inport_date varchar(200), modified_date varchar(200), OBJECTID int4, ownership int2, label varchar(3), olt_num varchar(3), des_type int2, metro_poh varchar(3), rack_label varchar(10), length int2, width int2, comments varchar(255), build_status int2, design_status int2, asb_label varchar(10), build_com varchar(255), globalid varchar(38), createdby varchar(255), creationdate timestamp, editedby varchar(255), editeddate timestamp
    -> BulkAttributeRenamer_23
BulkAttributeRenamer_23
    ATTRCHOICE_ACTION = NONPROTECTEDFME
    MODE_CHOICE = RENAME
    PATTERN_ACTION_DISP = ADDPREFIX
    REPLACE_STR = post_
    ATTRCHOICE = All Attributes
    -> DateTimeConverter_16
DateTimeConverter_16
    DATETIME_ATTR = post_modified_date
    IN_FORMAT = %Y%m%d%H%M
    OUT_FORMAT = %Y%m%d%H%M%S
    PASSTHROUGH = YES
    REPAIR_INPUT = YES
    -> FeatureMerger_8 [REQUESTOR]
Build_OLT (reader ARCGISONLINEFEATURES_2)
    attributes: OBJECTID OID, ownership SmallInteger, label String(3), olt_num String(3), des_type SmallInteger, metro_poh String(3), rack_label String(10), length SmallInteger, width SmallInteger, comments String(255), build_status SmallInteger, design_status SmallInteger, asb_label String(10), build_com String(255), globalid GlobalID(38), createdby String(255), creationdate Date, editedby String(255), editeddate Date
    -> BulkAttributeRenamer_22
BulkAttributeRenamer_22
    ATTRCHOICE_ACTION = NONPROTECTEDFME
    MODE_CHOICE = RENAME
    PATTERN_ACTION_DISP = ADDPREFIX
    REPLACE_STR = agol_
    ATTRCHOICE = All Attributes
    -> DateTimeConverter_17
DateTimeConverter_17
    DATETIME_ATTR = agol_editeddate
    IN_FORMAT = %Y%m%d%H%M
    OUT_FORMAT = %Y%m%d%H%M%S
    PASSTHROUGH = YES
    REPAIR_INPUT = YES
    -> FeatureMerger_8 [SUPPLIER]
FeatureMerger_8
    ATTR_ACCUM_MODE = Merge Supplier
    ATTR_CONFLICT_RES_LOOKUP = SUPPLIER_IF_CONFLICT
    IGNORE_NULLS = No
    JOIN_KEYS = @Value(post_globalid) @Value(agol_globalid) AUTO
    MERGE_TYPE_VAL = GEOM_AND_ATTRS
    PRESERVE_FEATURE_ORDER_LOOKUP = PER_OUTPUT_PORT
    PROCESS_DUPS = NO
    REJECT_NULL_MISSING_KEYS = No
    SUPPLIERS_FIRST = No
    ATTR_CONFLICT_RES = Use Supplier
    MERGE_TYPE = Attributes and Geometry
    MERGED -> Tester_8
Tester_8
    BOOL_OP = OR
    TEST_CLAUSE = DATETIME_TEST @Value(agol_editeddate) > @Value(post_modified_date)
    TEST_MODE = DATETIME_TEST
    PASSED -> BulkAttributeRemover_8
BulkAttributeRemover_8
    ATTR_EXP = post_
    -> BulkAttributeRenamer_24
BulkAttributeRenamer_24
    ATTRCHOICE_ACTION = NONPROTECTEDFME
    CASE_DISP = YES
    MODE_CHOICE = RENAME
    PATTERN_ACTION_DISP = REMOVEPREFIX
    REPLACE_STR = agol_
    ATTRCHOICE = All Attributes
    -> AttributeManager_8
AttributeManager_8
    ATTR_TABLE = RENAME_SET_VALUE OBJECTID > objectid
    USER_EXPOSED_ATTRIBUTES = agol_OBJECTID,agol_level_,agol_homes,agol_name,agol_GlobalID,agol_CreatedBy,agol_CreationDate,agol_EditedBy,agol_EditedDate,agol_Shape__Area,agol_Shape__Length,post_inport_date,post_modified_date,post_level,post_OBJECTID,post_homes,post_name,post_GlobalID,post_CreatedBy,post_CreationDate,post_EditedBy,post_EditedDate,post_Shape__Area,post_Shape__Length,OBJECTID,level_,homes,name,GlobalID,CreatedBy,CreationDate,EditedBy,EditedDate,Shape__Area,Shape__Length,status,label,ownership,type,location_a,surface_ty,comments,drop_tag,visible,use_,ch_access,condition,lid_con,duct_cou,reason_for,dp_capacit,nbi_enc,ch_area,exchange,dub_pro,eir_label,start_end,sd_meet,nbi_sd,cut_con,hazard,ribbon,build_status,design_status,asb_core,asb_label,build_com,bldg_id,address,eircode,address_st,hhp_res,hhp_com,floors,new_prem,odp_label,prem_status,drop_code,route_surv,cross_oh,cross_ug,cross_prop,duct_stat,calc_lengt,olt_num,des_type,metro_poh,rack_label,length,width,globalid,createdby,creationdate,editedby,editeddate
    -> olt (writer POSTGIS_2)
olt (writer POSTGIS_2)
    attributes: inport_date varchar(200), modified_date varchar(200), objectid int4, ownership int2, label varchar(3), olt_num varchar(3), des_type int2, metro_poh varchar(3), rack_label varchar(10), length int2, width int2, comments varchar(255), build_status int2, design_status int2, asb_label varchar(10), build_com varchar(255), globalid varchar(38), createdby varchar(255), creationdate timestamp, editedby varchar(255), editeddate timestamp

Bookmark: Pole
pole (reader POSTGIS_3)
    attributes: inport_date varchar(200), modified_date varchar(200), use int2, OBJECTID int4, status int2, ownership int2, label varchar(15), barcode varchar(9), height float8, height_rea int2, build_clas int2, location_a int2, location_s int2, stay_type int2, attachment int2, comments varchar(255), drop_tags varchar(20), add_repair int2, confirm_po int2, po_access int2, birth_vis int2, birth_hgt float8, pole_veg int2, cop_cab int2, fib_cab int2, dp_capacit int2, stay_no int2, ad_rep_rea int2, hammer int2, prod int2,
      soil_sta int2, type int2, po_area int2, sub_term int2, exchange varchar(5), lea int2, date_sur timestamp, nbi_furn int2, ex_hardwar int2, pass_fai int2, fail_reasn int2, rep_pole int2, hazard int2, esb_conf int2, timb_type int2, age int2, ribbon varchar(5), build_status int2, design_status int2, asb_bar varchar(10), build_com varchar(255), globalid varchar(38), createdby varchar(255), creationdate timestamp, editedby varchar(255), editeddate timestamp, way_type int2
    -> BulkAttributeRenamer_26
BulkAttributeRenamer_26
    ATTRCHOICE_ACTION = NONPROTECTEDFME
    MODE_CHOICE = RENAME
    PATTERN_ACTION_DISP = ADDPREFIX
    REPLACE_STR = post_
    ATTRCHOICE = All Attributes
    -> DateTimeConverter_18
DateTimeConverter_18
    DATETIME_ATTR = post_modified_date
    IN_FORMAT = %Y%m%d%H%M
    OUT_FORMAT = %Y%m%d%H%M%S
    PASSTHROUGH = YES
    REPAIR_INPUT = YES
    -> FeatureMerger_9 [REQUESTOR]
Build_Pole (reader ARCGISONLINEFEATURES_2)
    attributes: OBJECTID OID, status SmallInteger, ownership SmallInteger, label String(15), barcode String(9), height Double, height_rea SmallInteger, build_clas SmallInteger, location_a SmallInteger, location_s SmallInteger, stay_type SmallInteger, attachment SmallInteger, comments String(255), drop_tags String(20), add_repair SmallInteger, confirm_po SmallInteger, po_access SmallInteger, birth_vis SmallInteger, birth_hgt Double, cop_cab SmallInteger, fib_cab SmallInteger, dp_capacit SmallInteger, stay_no SmallInteger, ad_rep_rea SmallInteger, hammer SmallInteger, prod SmallInteger, soil_sta SmallInteger, type SmallInteger, po_area SmallInteger, sub_term SmallInteger,
      use_ SmallInteger, exchange String(5), lea SmallInteger, date_sur Date, nbi_furn SmallInteger, ex_hardwar SmallInteger, pass_fai SmallInteger, fail_reasn SmallInteger, rep_pole SmallInteger, hazard SmallInteger, esb_conf SmallInteger, timb_type SmallInteger, age SmallInteger, ribbon String(5), build_status SmallInteger, design_status SmallInteger, asb_bar String(10), build_com String(255), globalid GlobalID(38), createdby String(255), creationdate Date, editedby String(255), editeddate Date, pole_veg SmallInteger
    -> BulkAttributeRenamer_25
BulkAttributeRenamer_25
    ATTRCHOICE_ACTION = NONPROTECTEDFME
    MODE_CHOICE = RENAME
    PATTERN_ACTION_DISP = ADDPREFIX
    REPLACE_STR = agol_
    ATTRCHOICE = All Attributes
    -> DateTimeConverter_19
DateTimeConverter_19
    DATETIME_ATTR = agol_editeddate
    IN_FORMAT = %Y%m%d%H%M
    OUT_FORMAT = %Y%m%d%H%M%S
    PASSTHROUGH = YES
    REPAIR_INPUT = YES
    -> FeatureMerger_9 [SUPPLIER]
FeatureMerger_9
    ATTR_ACCUM_MODE = Merge Supplier
    ATTR_CONFLICT_RES_LOOKUP = SUPPLIER_IF_CONFLICT
    IGNORE_NULLS = No
    JOIN_KEYS = @Value(post_globalid) @Value(agol_globalid) AUTO
    MERGE_TYPE_VAL = GEOM_AND_ATTRS
    PRESERVE_FEATURE_ORDER_LOOKUP = PER_OUTPUT_PORT
    PROCESS_DUPS = NO
    REJECT_NULL_MISSING_KEYS = No
    SUPPLIERS_FIRST = No
    ATTR_CONFLICT_RES = Use Supplier
    MERGE_TYPE = Attributes and Geometry
    MERGED -> Tester_9
Tester_9
    BOOL_OP = OR
    TEST_CLAUSE = DATETIME_TEST @Value(agol_editeddate) > @Value(post_modified_date)
    TEST_MODE = DATETIME_TEST
    PASSED -> BulkAttributeRemover_9
BulkAttributeRemover_9
    ATTR_EXP = post_
    -> BulkAttributeRenamer_27
BulkAttributeRenamer_27
    ATTRCHOICE_ACTION = NONPROTECTEDFME
    CASE_DISP = YES
    MODE_CHOICE = RENAME
    PATTERN_ACTION_DISP = REMOVEPREFIX
    REPLACE_STR = agol_
    ATTRCHOICE = All Attributes
    -> AttributeManager_9
AttributeManager_9
    ATTR_TABLE:
      RENAME_SET_VALUE OBJECTID > objectid
      RENAME_SET_VALUE use_ > use
    USER_EXPOSED_ATTRIBUTES = agol_OBJECTID,agol_level_,agol_homes,agol_name,agol_GlobalID,agol_CreatedBy,agol_CreationDate,agol_EditedBy,agol_EditedDate,agol_Shape__Area,agol_Shape__Length,post_inport_date,post_modified_date,post_level,post_OBJECTID,post_homes,post_name,post_GlobalID,post_CreatedBy,post_CreationDate,post_EditedBy,post_EditedDate,post_Shape__Area,post_Shape__Length,OBJECTID,level_,homes,name,GlobalID,CreatedBy,CreationDate,EditedBy,EditedDate,Shape__Area,Shape__Length,status,label,ownership,type,location_a,surface_ty,comments,drop_tag,visible,use_,ch_access,condition,lid_con,duct_cou,reason_for,dp_capacit,nbi_enc,ch_area,exchange,dub_pro,eir_label,start_end,sd_meet,nbi_sd,cut_con,hazard,ribbon,build_status,design_status,asb_core,asb_label,build_com,bldg_id,address,eircode,address_st,hhp_res,hhp_com,floors,new_prem,odp_label,prem_status,drop_code,route_surv,cross_oh,cross_ug,cross_prop,duct_stat,calc_lengt,barcode,height,height_rea,build_clas,location_s,stay_type,attachment,drop_tags,add_repair,confirm_po,po_access,birth_vis,birth_hgt,veg,cop_cab,fib_cab,stay_no,ad_rep_rea,hammer,prod,soil_sta,po_area,sub_term,lea,date_sur,nbi_furn,ex_hardwar,pass_fai,fail_reasn,rep_pole,esb_conf,timb_type,age,asb_bar,globalid,createdby,creationdate,editedby,editeddate
    -> pole (writer POSTGIS_2)
pole (writer POSTGIS_2)
    attributes: inport_date varchar(200), modified_date varchar(200), use int2, objectid int4, status int2, ownership int2, label varchar(15), barcode varchar(9), height float8, height_rea int2, build_clas int2, location_a int2, location_s int2, stay_type int2, attachment int2, comments varchar(255), drop_tags varchar(20), add_repair int2, confirm_po int2, po_access int2, birth_vis int2, birth_hgt float8, veg int2, cop_cab int2, fib_cab int2, dp_capacit int2, stay_no int2, ad_rep_rea int2, hammer int2, prod int2,
      soil_sta int2, type int2, po_area int2, sub_term int2, exchange varchar(5), lea int2, date_sur timestamp, nbi_furn int2, ex_hardwar int2, pass_fai int2, fail_reasn int2, rep_pole int2, hazard int2, esb_conf int2, timb_type int2, age int2, ribbon varchar(5), build_status int2, design_status int2, asb_bar varchar(10), build_com varchar(255), globalid varchar(38), createdby varchar(255), creationdate timestamp, editedby varchar(255), editeddate timestamp

Bookmark: SED
sed (reader POSTGIS_3)
    attributes: inport_date varchar(200), modified_date varchar(200), OBJECTID int4, label varchar(16), sed_type int2, notes varchar(255), build_status int2, design_status int2, asb_len float4, build_com varchar(255), globalid varchar(38), createdby varchar(255), creationdate timestamp, editedby varchar(255), editeddate timestamp
    -> BulkAttributeRenamer_29
BulkAttributeRenamer_29
    ATTRCHOICE_ACTION = NONPROTECTEDFME
    MODE_CHOICE = RENAME
    PATTERN_ACTION_DISP = ADDPREFIX
    REPLACE_STR = post_
    ATTRCHOICE = All Attributes
    -> DateTimeConverter_20
DateTimeConverter_20
    DATETIME_ATTR = post_modified_date
    IN_FORMAT = %Y%m%d%H%M
    OUT_FORMAT = %Y%m%d%H%M%S
    PASSTHROUGH = YES
    REPAIR_INPUT = YES
    -> FeatureMerger_10 [REQUESTOR]
Build_SED (reader ARCGISONLINEFEATURES_2)
    attributes: OBJECTID OID, label String(16), sed_type SmallInteger, notes String(255), build_status SmallInteger, design_status SmallInteger, asb_len Single, build_com String(255), globalid GlobalID(38), createdby String(255), creationdate Date, editedby String(255), editeddate Date
    -> BulkAttributeRenamer_28
BulkAttributeRenamer_28
    ATTRCHOICE_ACTION = NONPROTECTEDFME
    MODE_CHOICE = RENAME
    PATTERN_ACTION_DISP = ADDPREFIX
    REPLACE_STR = agol_
    ATTRCHOICE = All Attributes
    -> DateTimeConverter_21
DateTimeConverter_21
    DATETIME_ATTR = agol_editeddate
    IN_FORMAT = %Y%m%d%H%M
    OUT_FORMAT = %Y%m%d%H%M%S
    PASSTHROUGH = YES
    REPAIR_INPUT = YES
    -> FeatureMerger_10 [SUPPLIER]
FeatureMerger_10
    ATTR_ACCUM_MODE = Merge Supplier
    ATTR_CONFLICT_RES_LOOKUP = SUPPLIER_IF_CONFLICT
    IGNORE_NULLS = No
    JOIN_KEYS = @Value(post_globalid) @Value(agol_globalid) AUTO
    MERGE_TYPE_VAL = GEOM_AND_ATTRS
    PRESERVE_FEATURE_ORDER_LOOKUP = PER_OUTPUT_PORT
    PROCESS_DUPS = NO
    REJECT_NULL_MISSING_KEYS = No
    SUPPLIERS_FIRST = No
    ATTR_CONFLICT_RES = Use Supplier
    MERGE_TYPE = Attributes and Geometry
    MERGED -> Tester_10
Tester_10
    BOOL_OP = OR
    TEST_CLAUSE = DATETIME_TEST @Value(agol_editeddate) > @Value(post_modified_date)
    TEST_MODE = DATETIME_TEST
    PASSED -> BulkAttributeRemover_10
BulkAttributeRemover_10
    ATTR_EXP = post_
    -> BulkAttributeRenamer_30
BulkAttributeRenamer_30
    ATTRCHOICE_ACTION = NONPROTECTEDFME
    CASE_DISP = YES
    MODE_CHOICE = RENAME
    PATTERN_ACTION_DISP = REMOVEPREFIX
    REPLACE_STR = agol_
    ATTRCHOICE = All Attributes
    -> AttributeManager_10
AttributeManager_10
    ATTR_TABLE = RENAME_SET_VALUE OBJECTID > objectid
    USER_EXPOSED_ATTRIBUTES = agol_OBJECTID,agol_level_,agol_homes,agol_name,agol_GlobalID,agol_CreatedBy,agol_CreationDate,agol_EditedBy,agol_EditedDate,agol_Shape__Area,agol_Shape__Length,post_inport_date,post_modified_date,post_level,post_OBJECTID,post_homes,post_name,post_GlobalID,post_CreatedBy,post_CreationDate,post_EditedBy,post_EditedDate,post_Shape__Area,post_Shape__Length,OBJECTID,level_,homes,name,GlobalID,CreatedBy,CreationDate,EditedBy,EditedDate,Shape__Area,Shape__Length,status,label,ownership,type,location_a,surface_ty,comments,drop_tag,visible,use_,ch_access,condition,lid_con,duct_cou,reason_for,dp_capacit,nbi_enc,ch_area,exchange,dub_pro,eir_label,start_end,sd_meet,nbi_sd,cut_con,hazard,ribbon,build_status,design_status,asb_core,asb_label,build_com,bldg_id,address,eircode,address_st,hhp_res,hhp_com,floors,new_prem,odp_label,prem_status,drop_code,route_surv,cross_oh,cross_ug,cross_prop,duct_stat,calc_lengt,sed_type,notes,asb_len,globalid,createdby,creationdate,editedby,editeddate
    -> sed (writer POSTGIS_2)
sed (writer POSTGIS_2)
    attributes: inport_date varchar(200), modified_date varchar(200), objectid int4, label varchar(16), sed_type int2, notes varchar(255), build_status int2, design_status int2, asb_len float4, build_com varchar(255), globalid varchar(38), createdby varchar(255), creationdate timestamp, editedby varchar(255), editeddate timestamp

Bookmark: Span
span (reader POSTGIS_3)
    attributes: inport_date varchar(200), modified_date varchar(200), use int2, OBJECTID int4, label varchar(16), status int2, span_type int2, span_acces int2, el_cross_v int2, drop_tags varchar(40), trench_ty int2, surface_ty int2, route_len float8, ribbon varchar(5), tree_dens int2, tree_len float8, low_cab float8, low_cros int2, comments varchar(255), build_status int2, design_status int2, asb_len float4, build_com varchar(255), surv_ttlen float4, surv_dens int2, asb_ttlen float4, asb_dens int2, tt_issues int2, globalid varchar(38), createdby varchar(255),
      creationdate timestamp, editedby varchar(255), editeddate timestamp, Shape__Length float8, lidar_access int2, lidar_lin varchar(1000), lmo_len float4, tt_req int2, sub_by int2, sub_com int2, photo_ev int2, lidar_iss int2, nbi_com varchar(1000), qc_sta int2, qa_len float4, span_clear float4, tt_clear float4, qa_comm varchar(1000), photo_stn int2, qc_stat int2, sample int2, attach_count float4, _part_count numeric(20,0), surface_gv float8, surface_fw float8, surface_cw float8, surface_rc float8
    -> BulkAttributeRenamer_32
BulkAttributeRenamer_32
    ATTRCHOICE_ACTION = NONPROTECTEDFME
    MODE_CHOICE = RENAME
    PATTERN_ACTION_DISP = ADDPREFIX
    REPLACE_STR = post_
    ATTRCHOICE = All Attributes
    -> DateTimeConverter_22
DateTimeConverter_22
    DATETIME_ATTR = post_modified_date
    IN_FORMAT = %Y%m%d%H%M
    OUT_FORMAT = %Y%m%d%H%M%S
    PASSTHROUGH = YES
    REPAIR_INPUT = YES
    -> FeatureMerger_11 [REQUESTOR]
Build_Span (reader ARCGISONLINEFEATURES_2)
    attributes: OBJECTID OID, label String(16), status SmallInteger, span_type SmallInteger, span_acces SmallInteger, el_cross_v SmallInteger, drop_tags String(40), trench_ty SmallInteger, surface_ty SmallInteger, route_len Double, ribbon String(5), use_ SmallInteger, tree_dens SmallInteger, tree_len Double, low_cab Double, low_cros SmallInteger, comments String(255), build_status SmallInteger, design_status SmallInteger, asb_len Single, build_com String(255), surv_ttlen Single, surv_dens SmallInteger, asb_ttlen Single, asb_dens SmallInteger, tt_issues SmallInteger, globalid GlobalID(38), createdby String(255), creationdate Date, editedby String(255),
      editeddate Date, Shape__Length Double, lidar_access SmallInteger, lidar_lin String(1000), lmo_len Single, tt_req SmallInteger, sub_by SmallInteger, sub_com SmallInteger, photo_ev SmallInteger, lidar_iss SmallInteger, nbi_com String(1000), qc_sta SmallInteger, qa_len Single, span_clear Single, tt_clear Single, qa_comm String(1000), photo_stn SmallInteger, qc_stat SmallInteger, sample SmallInteger, attach_count Single, surface_gv Double, surface_fw Double, surface_cw Double, surface_rc Double
    -> BulkAttributeRenamer_31
BulkAttributeRenamer_31
    ATTRCHOICE_ACTION = NONPROTECTEDFME
    MODE_CHOICE = RENAME
    PATTERN_ACTION_DISP = ADDPREFIX
    REPLACE_STR = agol_
    ATTRCHOICE = All Attributes
    -> DateTimeConverter_23
DateTimeConverter_23
    DATETIME_ATTR = agol_editeddate
    IN_FORMAT = %Y%m%d%H%M
    OUT_FORMAT = %Y%m%d%H%M%S
    PASSTHROUGH = YES
    REPAIR_INPUT = YES
    -> FeatureMerger_11 [SUPPLIER]
FeatureMerger_11
    ATTR_ACCUM_MODE = Merge Supplier
    ATTR_CONFLICT_RES_LOOKUP = SUPPLIER_IF_CONFLICT
    IGNORE_NULLS = No
    JOIN_KEYS = @Value(post_globalid) @Value(agol_globalid) AUTO
    MERGE_TYPE_VAL = GEOM_AND_ATTRS
    PRESERVE_FEATURE_ORDER_LOOKUP = PER_OUTPUT_PORT
    PROCESS_DUPS = NO
    REJECT_NULL_MISSING_KEYS = No
    SUPPLIERS_FIRST = No
    ATTR_CONFLICT_RES = Use Supplier
    MERGE_TYPE = Attributes and Geometry
    MERGED -> Tester_11
Tester_11
    BOOL_OP = OR
    TEST_CLAUSE = DATETIME_TEST @Value(agol_editeddate) > @Value(post_modified_date)
    TEST_MODE = DATETIME_TEST
    PASSED -> BulkAttributeRemover_11
BulkAttributeRemover_11
    ATTR_EXP = post_
    -> BulkAttributeRenamer_33
BulkAttributeRenamer_33
    ATTRCHOICE_ACTION = NONPROTECTEDFME
    CASE_DISP = YES
    MODE_CHOICE = RENAME
    PATTERN_ACTION_DISP = REMOVEPREFIX
    REPLACE_STR = agol_
    ATTRCHOICE = All Attributes
    -> AttributeManager_11
AttributeManager_11
    ATTR_TABLE:
      RENAME_SET_VALUE OBJECTID > objectid
      RENAME_SET_VALUE use_ > use
    USER_EXPOSED_ATTRIBUTES = agol_OBJECTID,agol_level_,agol_homes,agol_name,agol_GlobalID,agol_CreatedBy,agol_CreationDate,agol_EditedBy,agol_EditedDate,agol_Shape__Area,agol_Shape__Length,post_inport_date,post_modified_date,post_level,post_OBJECTID,post_homes,post_name,post_GlobalID,post_CreatedBy,post_CreationDate,post_EditedBy,post_EditedDate,post_Shape__Area,post_Shape__Length,OBJECTID,level_,homes,name,GlobalID,CreatedBy,CreationDate,EditedBy,EditedDate,Shape__Area,Shape__Length,status,label,ownership,type,location_a,surface_ty,comments,drop_tag,visible,use_,ch_access,condition,lid_con,duct_cou,reason_for,dp_capacit,nbi_enc,ch_area,exchange,dub_pro,eir_label,start_end,sd_meet,nbi_sd,cut_con,hazard,ribbon,build_status,design_status,asb_core,asb_label,build_com,bldg_id,address,eircode,address_st,hhp_res,hhp_com,floors,new_prem,odp_label,prem_status,drop_code,route_surv,cross_oh,cross_ug,cross_prop,duct_stat,calc_lengt,span_type,span_acces,el_cross_v,drop_tags,trench_ty,route_len,tree_dens,tree_len,low_cab,low_cros,asb_len,surv_ttlen,surv_dens,asb_ttlen,asb_dens,tt_issues,lidar_access,lidar_lin,lmo_len,tt_req,sub_by,sub_com,photo_ev,lidar_iss,nbi_com,qc_sta,qa_len,span_clear,tt_clear,qa_comm,photo_stn,qc_stat,globalid,createdby,creationdate,editedby,editeddate
    -> span (writer POSTGIS_2)
span (writer POSTGIS_2)
    attributes: inport_date varchar(200), modified_date varchar(200), use int2, objectid int4, label varchar(16), status int2, span_type int2, span_acces int2, el_cross_v int2, drop_tags varchar(40), trench_ty int2, surface_ty int2, route_len float8, ribbon varchar(5), tree_dens int2, tree_len float8, low_cab float8, low_cros int2, comments varchar(255), build_status int2, design_status int2, asb_len float4, build_com varchar(255), surv_ttlen float4, surv_dens int2, asb_ttlen float4, asb_dens int2, tt_issues int2, globalid varchar(38), createdby varchar(255),
      creationdate timestamp, editedby varchar(255), editeddate timestamp, shape__length float8, lidar_access int2, lidar_lin varchar(1000), lmo_len float4, tt_req int2, sub_by int2, sub_com int2, photo_ev int2, lidar_iss int2, nbi_com varchar(1000), qc_sta int2, qa_len float4, span_clear float4, tt_clear float4, qa_comm varchar(1000), photo_stn int2, qc_stat int2, sample int2, attach_count float4, _part_count numeric(20,0)

Bookmark: Splice Closure
splice_closures (reader POSTGIS_3)
    attributes: inport_date varchar(200), modified_date varchar(200), OBJECTID int4, label varchar(8), enc_type int2, enc_size int2, stru_label varchar(15), placement int2, sp1_type int2, sp1_label varchar(16), sp2_type int2, sp2_label varchar(16), status int2, reel_end int2, ribbon varchar(5), comments varchar(255), build_status int2, design_status int2, asb_spl int2, asb_label varchar(16), build_com varchar(255), globalid varchar(38), createdby varchar(255), creationdate timestamp, editedby varchar(255), editeddate timestamp
    -> BulkAttributeRenamer_35
BulkAttributeRenamer_35
    ATTRCHOICE_ACTION = NONPROTECTEDFME
    MODE_CHOICE = RENAME
    PATTERN_ACTION_DISP = ADDPREFIX
    REPLACE_STR = post_
    ATTRCHOICE = All Attributes
    -> DateTimeConverter_24
DateTimeConverter_24
    DATETIME_ATTR = post_modified_date
    IN_FORMAT = %Y%m%d%H%M
    OUT_FORMAT = %Y%m%d%H%M%S
    PASSTHROUGH = YES
    REPAIR_INPUT = YES
    -> FeatureMerger_12 [REQUESTOR]
Build_SpliceClosures (reader ARCGISONLINEFEATURES_2)
    attributes: OBJECTID OID, label String(8), enc_type SmallInteger, enc_size SmallInteger, stru_label String(15), placement SmallInteger, sp1_type SmallInteger, sp1_label String(16), sp2_type SmallInteger, sp2_label String(16), status SmallInteger, reel_end SmallInteger, ribbon String(5), comments String(255), build_status SmallInteger, design_status SmallInteger, asb_spl SmallInteger, asb_label String(16), build_com String(255), globalid GlobalID(38), createdby String(255), creationdate Date, editedby String(255), editeddate Date
    -> BulkAttributeRenamer_34
BulkAttributeRenamer_34
    ATTRCHOICE_ACTION = NONPROTECTEDFME
    MODE_CHOICE = RENAME
    PATTERN_ACTION_DISP = ADDPREFIX
    REPLACE_STR = agol_
    ATTRCHOICE = All Attributes
    -> DateTimeConverter_25
DateTimeConverter_25
    DATETIME_ATTR = agol_editeddate
    IN_FORMAT = %Y%m%d%H%M
    OUT_FORMAT = %Y%m%d%H%M%S
    PASSTHROUGH = YES
    REPAIR_INPUT = YES
    -> FeatureMerger_12 [SUPPLIER]
FeatureMerger_12
    ATTR_ACCUM_MODE = Merge Supplier
    ATTR_CONFLICT_RES_LOOKUP = SUPPLIER_IF_CONFLICT
    IGNORE_NULLS = No
    JOIN_KEYS = @Value(post_globalid) @Value(agol_globalid) AUTO
    MERGE_TYPE_VAL = GEOM_AND_ATTRS
    PRESERVE_FEATURE_ORDER_LOOKUP = PER_OUTPUT_PORT
    PROCESS_DUPS = NO
    REJECT_NULL_MISSING_KEYS = No
    SUPPLIERS_FIRST = No
    ATTR_CONFLICT_RES = Use Supplier
    MERGE_TYPE = Attributes and Geometry
    MERGED -> Tester_12
Tester_12
    BOOL_OP = OR
    TEST_CLAUSE = DATETIME_TEST @Value(agol_editeddate) > @Value(post_modified_date)
    TEST_MODE = DATETIME_TEST
    PASSED -> BulkAttributeRemover_12
BulkAttributeRemover_12
    ATTR_EXP = post_
    -> BulkAttributeRenamer_36
BulkAttributeRenamer_36
    ATTRCHOICE_ACTION = NONPROTECTEDFME
    CASE_DISP = YES
    MODE_CHOICE = RENAME
    PATTERN_ACTION_DISP = REMOVEPREFIX
    REPLACE_STR = agol_
    ATTRCHOICE = All Attributes
    -> AttributeManager_12
AttributeManager_12
    ATTR_TABLE = RENAME_SET_VALUE OBJECTID > objectid
    USER_EXPOSED_ATTRIBUTES = agol_OBJECTID,agol_level_,agol_homes,agol_name,agol_GlobalID,agol_CreatedBy,agol_CreationDate,agol_EditedBy,agol_EditedDate,agol_Shape__Area,agol_Shape__Length,post_inport_date,post_modified_date,post_level,post_OBJECTID,post_homes,post_name,post_GlobalID,post_CreatedBy,post_CreationDate,post_EditedBy,post_EditedDate,post_Shape__Area,post_Shape__Length,OBJECTID,level_,homes,name,GlobalID,CreatedBy,CreationDate,EditedBy,EditedDate,Shape__Area,Shape__Length,status,label,ownership,type,location_a,surface_ty,comments,drop_tag,visible,use_,ch_access,condition,lid_con,duct_cou,reason_for,dp_capacit,nbi_enc,ch_area,exchange,dub_pro,eir_label,start_end,sd_meet,nbi_sd,cut_con,hazard,ribbon,build_status,design_status,asb_core,asb_label,build_com,bldg_id,address,eircode,address_st,hhp_res,hhp_com,floors,new_prem,odp_label,prem_status,drop_code,route_surv,cross_oh,cross_ug,cross_prop,duct_stat,calc_lengt,enc_type,enc_size,stru_label,placement,sp1_type,sp1_label,sp2_type,sp2_label,reel_end,asb_spl,globalid,createdby,creationdate,editedby,editeddate
    -> splice_closures (writer POSTGIS_2)
splice_closures (writer POSTGIS_2)
    attributes: inport_date varchar(200), modified_date varchar(200), objectid int4, label varchar(8), enc_type int2, enc_size int2, stru_label varchar(15), placement int2, sp1_type int2, sp1_label varchar(16), sp2_type int2, sp2_label varchar(16), status int2, reel_end int2, ribbon varchar(5), comments varchar(255), build_status int2, design_status int2, asb_spl int2, asb_label varchar(16), build_com varchar(255), globalid varchar(38), createdby varchar(255), creationdate timestamp, editedby varchar(255), editeddate timestamp

Bookmark: PostGIS
boundaries (reader POSTGIS_3)
    attributes: inport_date varchar(200), modified_date varchar(200), level int2, OBJECTID int4, homes int2, name varchar(20), comments varchar(255), globalid varchar(38), createdby varchar(255), creationdate timestamp, editedby varchar(255), editeddate timestamp, Shape__Area float8, Shape__Length float8
    -> BulkAttributeRenamer_2

Bookmark: Boundaries
BulkAttributeRenamer_2
    ATTRCHOICE_ACTION = NONPROTECTEDFME
    MODE_CHOICE = RENAME
    PATTERN_ACTION_DISP = ADDPREFIX
    REPLACE_STR = post_
    ATTRCHOICE = All Attributes
    -> DateTimeConverter_2
DateTimeConverter_2
    DATETIME_ATTR = post_modified_date
    IN_FORMAT = %Y%m%d%H%M
    OUT_FORMAT = %Y%m%d%H%M%S
    PASSTHROUGH = YES
    REPAIR_INPUT = YES
    -> FeatureMerger [REQUESTOR]
BulkAttributeRenamer
    ATTRCHOICE_ACTION = NONPROTECTEDFME
    MODE_CHOICE = RENAME
    PATTERN_ACTION_DISP = ADDPREFIX
    REPLACE_STR = agol_
    ATTRCHOICE = All Attributes
    -> DateTimeConverter_3
DateTimeConverter_3
    DATETIME_ATTR = agol_editeddate
    IN_FORMAT = %Y%m%d%H%M
    OUT_FORMAT = %Y%m%d%H%M%S
    PASSTHROUGH = YES
    REPAIR_INPUT = YES
    -> FeatureMerger [SUPPLIER]
FeatureMerger
    ATTR_ACCUM_MODE = Merge Supplier
    ATTR_CONFLICT_RES_LOOKUP = SUPPLIER_IF_CONFLICT
    IGNORE_NULLS = No
    JOIN_KEYS = @Value(post_globalid) @Value(agol_globalid) AUTO
    MERGE_TYPE_VAL = GEOM_AND_ATTRS
    PRESERVE_FEATURE_ORDER_LOOKUP = PER_OUTPUT_PORT
    PROCESS_DUPS = NO
    REJECT_NULL_MISSING_KEYS = No
    SUPPLIERS_FIRST = No
    ATTR_CONFLICT_RES = Use Supplier
    MERGE_TYPE = Attributes and Geometry
    MERGED -> Tester
Tester
    BOOL_OP = OR
    TEST_CLAUSE = DATETIME_TEST @Value(agol_editeddate) > @Value(post_modified_date)
    TEST_MODE = DATETIME_TEST
    PASSED -> BulkAttributeRemover
BulkAttributeRemover
    ATTR_EXP = post_
    -> BulkAttributeRenamer_3
BulkAttributeRenamer_3
    ATTRCHOICE_ACTION = NONPROTECTEDFME
    CASE_DISP = YES
    MODE_CHOICE = RENAME
    PATTERN_ACTION_DISP = REMOVEPREFIX
    REPLACE_STR = agol_
    ATTRCHOICE = All Attributes
    -> AttributeManager
AttributeManager
    ATTR_TABLE:
      RENAME_SET_VALUE OBJECTID > objectid
      RENAME_SET_VALUE level_ > level
    USER_EXPOSED_ATTRIBUTES = agol_OBJECTID,agol_level_,agol_homes,agol_name,agol_GlobalID,agol_CreatedBy,agol_CreationDate,agol_EditedBy,agol_EditedDate,agol_Shape__Area,agol_Shape__Length,post_inport_date,post_modified_date,post_level,post_OBJECTID,post_homes,post_name,post_GlobalID,post_CreatedBy,post_CreationDate,post_EditedBy,post_EditedDate,post_Shape__Area,post_Shape__Length,OBJECTID,level_,homes,name,GlobalID,CreatedBy,CreationDate,EditedBy,EditedDate,Shape__Area,Shape__Length,comments,globalid,createdby,creationdate,editedby,editeddate
    -> boundaries (writer POSTGIS_2)
boundaries (writer POSTGIS_2)
    attributes: inport_date varchar(200), modified_date varchar(200), level int2, objectid int4, homes int2, name varchar(20), comments varchar(255), globalid varchar(38), createdby varchar(255), creationdate timestamp, editedby varchar(255), editeddate timestamp, shape__area float8, shape__length float8

Bookmark: ArcGIS
Build_Boundaries (reader ARCGISONLINEFEATURES_2)
    attributes: OBJECTID OID, level_ SmallInteger, homes SmallInteger, name String(20), comments String(255), globalid GlobalID(38), createdby String(255), creationdate Date, editedby String(255), editeddate Date, Shape__Area Double, Shape__Length Double
    -> BulkAttributeRenamer

Bookmark: Chamber
chambers (reader POSTGIS_3)
    attributes: inport_date varchar(200), modified_date varchar(200), use int2, OBJECTID int4, status int2, label varchar(15), ownership int2, type int2, location_a int2, surface_ty int2, comments varchar(255), drop_tag varchar(20), visible int2, ch_access int2, condition int2, lid_con int2, duct_cou int2, reason_for int2, dp_capacit int2, nbi_enc int2, ch_area int2, exchange varchar(5), dub_pro int2, eir_label varchar(16), start_end int2, sd_meet int2, nbi_sd int2, cut_con int2, hazard int2, ribbon varchar(5),
      build_status int2, design_status int2, asb_core int2, asb_label varchar(15), build_com varchar(255), globalid varchar(38), createdby varchar(255), creationdate timestamp, editedby varchar(255), editeddate timestamp, ipid text, way_type int2
    -> BulkAttributeRenamer_5
BulkAttributeRenamer_5
    ATTRCHOICE_ACTION = NONPROTECTEDFME
    MODE_CHOICE = RENAME
    PATTERN_ACTION_DISP = ADDPREFIX
    REPLACE_STR = post_
    ATTRCHOICE = All Attributes
    -> DateTimeConverter_4
DateTimeConverter_4
    DATETIME_ATTR = post_modified_date
    IN_FORMAT = %Y%m%d%H%M
    OUT_FORMAT = %Y%m%d%H%M%S
    PASSTHROUGH = YES
    REPAIR_INPUT = YES
    -> FeatureMerger_2 [REQUESTOR]
Build_Chambers (reader ARCGISONLINEFEATURES_2)
    attributes: OBJECTID OID, status SmallInteger, label String(15), ownership SmallInteger, type SmallInteger, location_a SmallInteger, surface_ty SmallInteger, comments String(255), drop_tag String(20), visible SmallInteger, use_ SmallInteger, ch_access SmallInteger, condition SmallInteger, lid_con SmallInteger, duct_cou SmallInteger, reason_for SmallInteger, dp_capacit SmallInteger, nbi_enc SmallInteger, ch_area SmallInteger, exchange String(5), dub_pro SmallInteger, eir_label String(16), start_end SmallInteger, sd_meet SmallInteger, nbi_sd SmallInteger, cut_con SmallInteger, hazard SmallInteger, ribbon String(5), build_status SmallInteger, design_status SmallInteger,
      asb_core SmallInteger, asb_label String(15), build_com String(255), globalid GlobalID(38), createdby String(255), creationdate Date, editedby String(255), editeddate Date, ipid String(13)
    -> BulkAttributeRenamer_4
BulkAttributeRenamer_4
    ATTRCHOICE_ACTION = NONPROTECTEDFME
    MODE_CHOICE = RENAME
    PATTERN_ACTION_DISP = ADDPREFIX
    REPLACE_STR = agol_
    ATTRCHOICE = All Attributes
    -> DateTimeConverter_5
DateTimeConverter_5
    DATETIME_ATTR = agol_editeddate
    IN_FORMAT = %Y%m%d%H%M
    OUT_FORMAT = %Y%m%d%H%M%S
    PASSTHROUGH = YES
    REPAIR_INPUT = YES
    -> FeatureMerger_2 [SUPPLIER]
FeatureMerger_2
    ATTR_ACCUM_MODE = Merge Supplier
    ATTR_CONFLICT_RES_LOOKUP = SUPPLIER_IF_CONFLICT
    IGNORE_NULLS = No
    JOIN_KEYS = @Value(post_globalid) @Value(agol_globalid) AUTO
    MERGE_TYPE_VAL = GEOM_AND_ATTRS
    PRESERVE_FEATURE_ORDER_LOOKUP = PER_OUTPUT_PORT
    PROCESS_DUPS = NO
    REJECT_NULL_MISSING_KEYS = No
    SUPPLIERS_FIRST = No
    ATTR_CONFLICT_RES = Use Supplier
    MERGE_TYPE = Attributes and Geometry
    MERGED -> Tester_2
Tester_2
    BOOL_OP = OR
    TEST_CLAUSE = DATETIME_TEST @Value(agol_editeddate) > @Value(post_modified_date)
    TEST_MODE = DATETIME_TEST
    PASSED -> BulkAttributeRemover_2
BulkAttributeRemover_2
    ATTR_EXP = post_
    -> BulkAttributeRenamer_6
BulkAttributeRenamer_6
    ATTRCHOICE_ACTION = NONPROTECTEDFME
    CASE_DISP = YES
    MODE_CHOICE = RENAME
    PATTERN_ACTION_DISP = REMOVEPREFIX
    REPLACE_STR = agol_
    ATTRCHOICE = All Attributes
    -> AttributeManager_2
AttributeManager_2
    ATTR_TABLE:
      RENAME_SET_VALUE OBJECTID > objectid
      RENAME_SET_VALUE use_ > use
    USER_EXPOSED_ATTRIBUTES = agol_OBJECTID,agol_level_,agol_homes,agol_name,agol_GlobalID,agol_CreatedBy,agol_CreationDate,agol_EditedBy,agol_EditedDate,agol_Shape__Area,agol_Shape__Length,post_inport_date,post_modified_date,post_level,post_OBJECTID,post_homes,post_name,post_GlobalID,post_CreatedBy,post_CreationDate,post_EditedBy,post_EditedDate,post_Shape__Area,post_Shape__Length,OBJECTID,level_,homes,name,GlobalID,CreatedBy,CreationDate,EditedBy,EditedDate,Shape__Area,Shape__Length,status,label,ownership,type,location_a,surface_ty,comments,drop_tag,visible,use_,ch_access,condition,lid_con,duct_cou,reason_for,dp_capacit,nbi_enc,ch_area,exchange,dub_pro,eir_label,start_end,sd_meet,nbi_sd,cut_con,hazard,ribbon,build_status,design_status,asb_core,asb_label,build_com,globalid,createdby,creationdate,editedby,editeddate
    -> chambers (writer POSTGIS_2)
chambers (writer POSTGIS_2)
    attributes: inport_date varchar(200), modified_date varchar(200), use int2, objectid int4, status int2, label varchar(15), ownership int2, type int2, location_a int2, surface_ty int2, comments varchar(255), drop_tag varchar(20), visible int2, ch_access int2, condition int2, lid_con int2, duct_cou int2, reason_for int2, dp_capacit int2, nbi_enc int2, ch_area int2, exchange varchar(5), dub_pro int2, eir_label varchar(16), start_end int2, sd_meet int2, nbi_sd int2, cut_con int2, hazard int2, ribbon varchar(5),
      build_status int2, design_status int2, asb_core int2, asb_label varchar(15), build_com varchar(255), globalid varchar(38), createdby varchar(255), creationdate timestamp, editedby varchar(255), editeddate timestamp
